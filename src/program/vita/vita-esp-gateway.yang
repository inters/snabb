module vita-esp-gateway {
  // METADATA
  namespace vita:esp-gateway;
  prefix esp-gateway;

  // IMPORTS
  import ietf-yang-types { prefix yang; }
  import ietf-inet-types { prefix inet; }

  // APPLICATION MODEL
  description "
  A Vita configuration defines a private network interface and one or more
  public network interfaces for use by the gateway, a set of routes to other
  Vita nodes, and the gateway’s MTU among other miscellaneous operational
  parameters.

  EXAMPLE

    private-interface4 {
      pci 0c:00.0;
      ip 172.16.1.10;
      nexthop-ip 172.16.1.1;
    }

    public-interface4 {
      pci 0c:00.1;
      ip 203.0.113.10;
      nexthop-ip 172.16.1.1;
    }

    route4 {
      id site2;
      net 172.16.2.0/24;
      gateway { ip 203.0.113.2; }
      preshared-key 91440DA06376A668AC4959A840A125D75FB544E8AA25A08B813E49F0A4B2E270;
      spi 1001;
    }

    route4 {
      id site3;
      net 172.16.3.0/24;
      gateway { ip 203.0.113.3; }
      preshared-key CF0BDD7A058BE55C12B7F2AA30D23FF01BDF8BE6571F2019ED7F7EBD3DA97B47;
      spi 1223;
    }

    mtu 1280;

    ";

  choice gateway {
    description "
    Vita operates either in IPv4 more or in IPv6 mode.
    ";
    case v4 {
      description "
      To configure a IPv4 gateway, interfaces and routes must be declared with
      private-interface4, public-interface4, and route4.
      ";
      container private-interface4 {
        uses interface; uses interface4;
        description "
        A single private interface is operated in RSS mode to distribute
        streams onto work queues.
        ";
      }
      list public-interface4 {
        uses interface; uses interface4; uses overridable-queue; uses gateway;
        uses nat-ip4;
        key ip; unique queue;
        description "
        Outbound traffic is distributed onto work queues once it is received on
        the private interface. Each work queue (typically one per CPU core) is
        assigned a dedicated public interface on which to forward its traffic.

        If more than one public interface is configured then each one needs to
        have a unique queue identifier assigned. Multiple public interfaces can
        operate on the same hardware interface in VMDq mode. If XDP mode is
        used, the host must ensure that traffic to the interface ip is
        forwarded to the correct queue (i.e., using ethtool --config-nfc).
        ";
      }
      list route4 {
        uses route; uses route4;
        key id; unique spi; unique preshared-key; unique net;
        description "
        A route specifies a logical tunnel between from one Vita node to
        another.
        ";
        list gateway {
          uses gateway; uses gateway4;
          key ip; unique queue; min-elements 1;
          description "
          A route lists one or more destination gateways, typically one for
          each work queue. The gateway IP address identifies a remote public
          interface at the route’s destination.

          For a given route, a work queue will tunnel packets to the gateway
          associated to it via the queue identifier. If only one gateway is
          configured then the queue identifier is optional and defaults to 1.
          If there is no dedicated gateway configured for a work queue then
          that work queue will fall back to use the gateway for queue 1 if
          available.

          Note that for a given route there can only be a single pair of
          gateways operating at any given time, and authenticated key exchange
          (AKE) will fail unless the configurations at each end define a
          matching gateway pair.
          ";
        }
      }
    }
    case v6 {
      description "
      To configure a IPv6 gateway, interfaces and routes must be declared with
      private-interface6, public-interface6, and route6.
      ";
      container private-interface6 {
        uses interface; uses interface6;
        description "
        Identical to private-interface4 (see above) except that it uses IPv6
        addresses.
        ";
      }
      list public-interface6 {
        uses interface; uses interface6; uses overridable-queue; uses gateway;
        uses nat-ip6;
        key ip; unique queue;
        description "
        Identical to public-interface4 (see above) except that it uses IPv6
        addresses.
        ";
      }
      list route6 {
        key id; unique spi; unique preshared-key; unique net;
        uses route; uses route6;
        description "
        Identical to route4 (see above) except that it uses IPv6 addresses and
        network prefixes.
        ";
        list gateway {
          uses gateway; uses gateway6;
          key ip; unique queue; min-elements 1;
        }
      }
    }
  }

  grouping interface {
    description "
    Each interface is assigned a device identifier, an IP address, and an
    IP address of the next hop through which all packets leaving the interface
    will be routed.

    A device identifier can be either a Linux PCI bus address or Linux
    interface name (for use with XDP).

    If the Ethernet (MAC) address of the interface is not explicitly specified,
    it is automatically derived from its assigned IP address by prepending the
    bytes 2a:bb: or 3a:bb: to its least significant 32 bits depending on
    whether it is the private or public interface respectively.

    If a next hop’s MAC address is given Vita will skip ARP or ND look-up and
    address the next hop directly (this option is mainly intended for use in
    testing environments.)

    Public interfaces can have the device-queue option set which overrides
    automatic device queue selection. Use this option with caution as it can
    interfere with other users of the device.

    In cases where public interfaces are behind a NAT the nat-ip option must
    specify the translated network address as seen by its peer gateways. If
    neither the nat-ip or ip options match the gateway ip as seen by peers
    key exchange messages will fail to authenticate.
    ";
    choice link {
      case pci { leaf pci { type pci-address; mandatory true; } }
      case xdp { leaf ifname { type interface-name; mandatory true; } }
    }
    leaf mac { type yang:mac-address; }
    leaf nexthop-mac { type yang:mac-address; }
  }
  grouping interface4 {
    leaf ip { type inet:ipv4-address-no-zone; mandatory true; }
    leaf nexthop-ip { type inet:ipv4-address-no-zone; mandatory true; }
  }
  grouping interface6 {
    leaf ip { type inet:ipv6-address-no-zone; mandatory true; }
    leaf nexthop-ip { type inet:ipv6-address-no-zone; mandatory true; }
  }
  grouping overridable-queue {
    leaf device-queue { type queue; }
  }
  grouping nat-ip4 {
    leaf nat-ip { type inet:ipv4-address-no-zone; }
  }
  grouping nat-ip6 {
    leaf nat-ip { type inet:ipv6-address-no-zone; }
  }

  grouping route {
    description "
    Each route is given a unique, human readable identifier subnet and gateways
    are specified with an IP prefix in CIDR notation, and IP addresses
    respectively. Packets that arrive on the private interface and which are
    destined to a route’s specified IP subnetwork are tunneled to a destination
    gateway of that route.

    For authentication, each route is assigned a unique, pre-shared 256-bit
    key, encoded as a hexadecimal string (two digits for each octet, most
    significant digit first). Additionally, a unique Security Parameter Index
    (SPI), which must be a positive integer equal or greater than 256, is
    specified for tagging and associating key exchange protocol messages for a
    given route. Like the pre-shared key, the SPI must be the same for both
    ends of a route.

    A suitable key could be obtained using the following command:

      vita --keygen

    ";
    leaf id { type id; mandatory true; }
    leaf spi { type spi; mandatory true; }
    leaf preshared-key { type key32; mandatory true; }
  }
  grouping route4 {
    leaf net { type inet:ipv4-prefix; mandatory true; }
  }
  grouping route6 {
    leaf net { type inet:ipv6-prefix; mandatory true; }
  }

  grouping gateway {
    leaf queue { type queue; default 1;}
  }
  grouping gateway4 {
    leaf ip { type inet:ipv4-address-no-zone; mandatory true; }
  }
  grouping gateway6 {
    leaf ip { type inet:ipv6-address-no-zone; mandatory true; }
  }

  leaf mtu {
    type uint16 { range "0..8923"; }
    default 8923;
    description "
    Optionally, the gateway’s MTU (excluding Ethernet overhead) can be
    specified in bytes. The default and maximum permitted value is 8923. Since
    Vita performs neither fragmentation nor reassembly it may be necessary to
    adjust the next-hop MTU accordingly. Note that packets leaving the public
    interface will have an added packet size overhead due to encapsulation (up
    to 57 bytes for IPv4 and up to 77 bytes for IPv6.)
    ";
  }
  leaf tfc {
    type boolean;
    description "
    If enabled, pad packets to the MTU to provide “Traffic Flow
    Confidentiality” (TFC).
    ";
  }

  leaf protocol-port {
    description "
    The UDP port used for key exchange protocol messages.
    ";
    type inet:port-number;
    default 303;
  }

  leaf negotiation-ttl {
    description "
    While the default configuration should be generally applicable, the
    negotiation timeout for the authenticated key exchanges (AKE) can be
    specified in seconds.
    ";
    type time-to-live;
    default 5;
  }
  leaf sa-ttl {
    type time-to-live;
    default 600;
    description "
    The default lifetime of Security Associations (SA) is 10 minutes. Generally
    speaking, lower 'sa-ttl' values are more secure since each renegotiation
    implies a fresh set of session keys and hence a checkpoint with regard to
    perfect forward secrecy (PFS).
    ";
  }

  // Outbound and inbound SAs are configured automatically unless the
  // 'data-plane' toggle (see below) is set to true.
  list outbound-sa {
    uses sa; uses gateway;
    key "spi queue"; unique "route queue";
    description "
    Active outbound SAs. Each work queue can have at most one outbound SA per
    route. The queue identifier defaults to 1.
    ";
  }
  list inbound-sa {
    uses sa; uses gateway;
    key "spi queue";
    description "
    Active inbound SAs. Each work queue can have multiple inbound SAs per
    route. The queue identifier defaults to 1.
    ";
  }
  leaf data-plane {
    type boolean;
    description "
    If true, disables the built-in key manager and AKE negotiations. In this
    mode the options 'negotiation-ttl', 'sa-ttl' as well as 'route.spi' and
    'route.preshared-key are ignored, and the user is expected to configure
    'outbound-sa' and 'inbound-sa' themselves.
    ";
  }
  grouping sa {
    description "
    Each SA must name an existing route, an SPI equal or greater than 256, and
    specify a 128-bit key and a 32-bit salt respectively, encoded as
    hexadecimal strings (two digits for each octet, most significant digit
    first).
    ";
    leaf route { type id; mandatory true; } // Parent route identifier
    leaf spi { type spi; mandatory true; }
    leaf aead { type string; mandatory true; }
    leaf key { type key16; mandatory true; }
    leaf salt { type key4; mandatory true; }
  }

  // TYPES 
  typedef id { type string { pattern '[\w_]+'; } }
  typedef pci-address {
    type string {
      pattern '([0-9a-fA-F]{4}:)?[0-9a-fA-F]{2}:[0-9a-fA-F]{2}\.[0-9a-fA-F]';
    }
  }
  typedef spi { type uint32 { range "256..max"; } }
  typedef key32 { type string { pattern '([0-9a-fA-F]{2}\s*){32}'; } }
  typedef key16 { type string { pattern '([0-9a-fA-F]{2}\s*){16}'; } }
  typedef key4  { type string { pattern '([0-9a-fA-F]{2}\s*){4}'; } }
  typedef time-to-live { type uint32 { range "1..max"; } }
  typedef queue { type uint16 { range "1..max"; } }
  typedef interface-name { type string { pattern '[^/]{1,15}'; } }

  // APPLICATION STATE
  container gateway-state {
    config false;
    description "
    Vita exposes an extended set of gateway state counters for monitoring and
    troubleshooting. You can query the state of a live instance using

       snabb config get-state

    (this is not configuration data, it can not be written.)
    ";

    // Interface state
    container private-interface {
      uses interface-state;
      description
        "Private interface statistics.";
    }

    container public-interface {
      uses interface-state;
      description
        "Public interface statistics.";
    }

    grouping interface-state {
      leaf rxbytes {
        type yang:zero-based-counter64;
        description
          "Total bytes received.";
      }
      leaf rxpackets {
        type yang:zero-based-counter64;
        description
          "Total packets received.";
      }
      leaf rxmcast {
        type yang:zero-based-counter64;
        description
          "Count of multicast packets received.";
      }
      leaf rxbcast {
        type yang:zero-based-counter64;
        description
          "Count of broadcast packets received.";
      }
      leaf rxdrop {
        type yang:zero-based-counter64;
        description
          "Count of incoming packets that were dropped.";
      }
      leaf rxerrors {
        type yang:zero-based-counter64;
        description
          "Count of receive errors.";
      }
      leaf txbytes {
        type yang:zero-based-counter64;
        description
          "Total bytes transmitted.";
      }
      leaf txpackets {
        type yang:zero-based-counter64;
        description
          "Total packets transmitted.";
      }
      leaf txmcast {
        type yang:zero-based-counter64;
        description
          "Count of multicast packets transmitted.";
      }
      leaf txbcast {
        type yang:zero-based-counter64;
        description
          "Count of broadcast packets transmitted.";
      }
      leaf txdrop {
        type yang:zero-based-counter64;
        description
          "Count of outgoing packets that were dropped.";
      }
      leaf txerrors {
        type yang:zero-based-counter64;
        description
          "Count of transmit errors.";
      }
      leaf rxdmapackets {
        type yang:zero-based-counter64;
        description
          "Count of incoming packets that were copied to main memory.";
      }
    }

    // Next-hop state
    container private-next-hop {
      uses next-hop-state;
      description
        "Private next-hop events.";
    }

    container public-next-hop {
      uses next-hop-state;
      description
        "Public next-hop events.";
    }

    grouping next-hop-state {
      leaf arp-requests {
        type yang:zero-based-counter64;
        description
          "Count of ARP requests sent.";
      }
      leaf arp-replies {
        type yang:zero-based-counter64;
        description
          "Count of ARP replies sent.";
      }
      leaf arp-errors {
        type yang:zero-based-counter64;
        description
          "Count of declined ARP requests.";
      }
      leaf ns-requests {
        type yang:zero-based-counter64;
        description
          "Count IPv6 Neighbor Solicitations sent.";
      }
      leaf na-replies {
        type yang:zero-based-counter64;
        description
          "Count IPv6 Neighbor Advertisements sent.";
      }
      leaf nd-errors {
        type yang:zero-based-counter64;
        description
          "Count of declined or invalid ND solicitations/advertisements.";
      }
      leaf addresses-added {
        type yang:zero-based-counter64;
        description
          "Count of learned addresses.";
      }
      leaf addresses-updated {
        type yang:zero-based-counter64;
        description
          "Count of times an address was updated.";
      }
    }

    // Protocol dispatch state
    container private-dispatch {
      description
        "Protocol dispatch errors for packets received on the private
         interface.";

      leaf ethertype-errors {
        type yang:zero-based-counter64;
        description
          "Count of packets that were dropped because they had an unsupported
           Ethertype.";
      }
    }

    container public-dispatch {
      description
        "Protocol dispatch errors for packets received on the
         public interface.";

      leaf rxerrors {
        type yang:zero-based-counter64;
        description
          "Total number of unhandled packets.";
      }
      leaf ethertype-errors {
        type yang:zero-based-counter64;
        description
          "Count of packets that were dropped because they had an unsupported
           Ethertype.";
      }
      leaf protocol-errors {
        type yang:zero-based-counter64;
        description
          "Count of packets that were dropped because they were of an
           unsupported protocol.";
      }
      leaf fragment-errors {
        type yang:zero-based-counter64;
        description
          "Count of packets that were dropped because they were IP fragments.";
      }
    }

    container inbound-dispatch {
      description
        "Protocol dispatch errors inbound packets that were successfully
         decapsulated.";

      leaf protocol-errors {
        type yang:zero-based-counter64;
        description
          "Count of packets that were dropped because they were of an
           unsupported protocol.";
      }
    }

    // TTL state
    container outbound-ttl {
      uses time-to-live-state;
      description
        "TTL errors for outbound packets.";
    }

    container inbound-ttl {
      uses time-to-live-state;
      description
        "TTL errors for inbound packets.";
    }

    grouping time-to-live-state {
      leaf protocol-errors {
        type yang:zero-based-counter64;
        description
          "Count of packets that were dropped because their TTL reached zero.";
      }
      leaf checksum-errors {
        type yang:zero-based-counter64;
        description
          "Count of packets that were dropped because they had an invalid IP
           checksum.";
      }
    }

    // Router state
    container private-router {
      description
        "Routing errors for outbound packets (to be encapsulated.)";

      leaf rxerrors {
        type yang:zero-based-counter64;
        description
          "Total packets that were dropped because they were not routable.";
      }
      leaf route-errors {
        type yang:zero-based-counter64;
        description
          "Count of packets that were dropped because their destination did not
           match any configured route.";
      }
      leaf mtu-errors {
        type yang:zero-based-counter64;
        description
          "Count of packets that were dropped because they exceeded the MTU.";
      }
    }

    container public-router {
      description
        "Routing errors for inbound packets (to be decapsulated.)";

      leaf route-errors {
        type yang:zero-based-counter64;
        description
          "Count of inbound encapsulated packets that were dropped because
           their SPI did not match any configured SA.";
      }
    }

    // ICMP state
    container private-icmp4 {
      uses icmp4-state;
      description
        "ICMPv4 events on the private interface.";
    }
    container private-icmp6 {
      uses icmp6-state;
      description
        "ICMPv6 events on the private interface.";
    }

    container public-icmp4 {
      uses icmp4-state;
      description
        "ICMPv4 events on the public interface.";
    }
    container public-icmp6 {
      uses icmp6-state;
      description
        "ICMPv6 events on the public interface.";
    }

    container inbound-icmp4 {
      uses icmp4-state;
      description
        "ICMPv4 events triggered by encapsulated messages on the public
         interface.";
    }
    container inbound-icmp6 {
      uses icmp6-state;
      description
        "ICMPv6 events triggered by encapsulated messages on the public
         interface.";
    }

    grouping icmp4-state {
      leaf rxerrors {
        type yang:zero-based-counter64;
        description
          "Total ICMPv4 messages that were dropped because they were invalid.";
      }
      leaf protocol-errors {
        type yang:zero-based-counter64;
        description
          "Count of ICMPv4 messages that were dropped because their checksum
           was invalid, or they were IP fragments.";
      }
      leaf type-not-implemented-errors {
        type yang:zero-based-counter64;
        description
          "Count of ICMPv4 messages received that had an unrecognized type.";
      }
      leaf code-not-implemented-errors {
        type yang:zero-based-counter64;
        description
          "Count of ICMPv4 messages received that had an unrecognized code.";
      }
      leaf destination-unreachable {
        type yang:zero-based-counter64;
        description
          "Count of ICMPv4 messages received of type
           'destination unreachable'."; 
      }
      leaf net-unreachable {
        type yang:zero-based-counter64;
        description
          "Count of ICMPv4 'destination unreachable' messages received with
           code 'net unreachable'.";
      }
      leaf host-unreachable {
        type yang:zero-based-counter64;
        description
          "Count of ICMPv4 'destination unreachable' messages received with
           code 'host unreachable'.";
      }
      leaf protocol-unreachable {
        type yang:zero-based-counter64;
        description
          "Count of ICMPv4 'destination unreachable' messages received with
           code 'protocol unreachable'.";
      }
      leaf port-unreachable {
        type yang:zero-based-counter64;
        description
          "Count of ICMPv4 'destination unreachable' messages received with
           code 'port unreachable'.";
      }
      leaf fragmentation-needed {
        type yang:zero-based-counter64;
        description
          "Count of ICMPv4 'destination unreachable' messages received with
           code 'fragmentation needed and DF set'.";
      }
      leaf source-route-failed {
        type yang:zero-based-counter64;
        description
          "Count of ICMPv4 'destination unreachable' messages received with
           code 'source route failed'.";
      }
      leaf time-exceeded {
        type yang:zero-based-counter64;
        description
          "Count of ICMPv4 messages received of type
           'time exceeded'."; 
      }
      leaf transit-ttl-exceeded {
        type yang:zero-based-counter64;
        description
          "Count of ICMPv4 'time exceeded' messages received with code
           'time to live exceeded in transit'.";
      }
      leaf fragment-reassembly-time-exceeded {
        type yang:zero-based-counter64;
        description
          "Count of ICMPv4 'time exceeded' messages received with code
           'fragment reassembly time exceeded'.";
      }
      leaf parameter-problem {
        type yang:zero-based-counter64;
        description
          "Count of ICMPv4 messages received of type
           'parameter problem'."; 
      }
      leaf redirect {
        type yang:zero-based-counter64;
        description
          "Count of ICMPv4 messages received of type
           'redirect'."; 
      }
      leaf redirect-net {
        type yang:zero-based-counter64;
        description
          "Count of ICMPv4 'redirect' messages received with code
           'Redirect datagrams for the Network'.";
      }
      leaf redirect-host {
        type yang:zero-based-counter64;
        description
          "Count of ICMPv4 'redirect' messages received with code
           'Redirect datagrams for the Host'.";
      }
      leaf redirect-tos-net {
        type yang:zero-based-counter64;
        description
          "Count of ICMPv4 'redirect' messages received with code
           'Redirect datagrams for the Type of Service and Network'.";
      }
      leaf redirect-tos-host {
        type yang:zero-based-counter64;
        description
          "Count of ICMPv4 'redirect' messages received with code
           'Redirect datagrams for the Type of Service and Host'.";
      }
      leaf echo-request {
        type yang:zero-based-counter64;
        description
          "Count of ICMPv4 echo requests handled.";
      }
    }

    grouping icmp6-state {
      leaf rxerrors {
        type yang:zero-based-counter64;
        description
          "Total ICMPv6 messages that were dropped because they were invalid.";
      }
      leaf protocol-errors {
        type yang:zero-based-counter64;
        description
          "Count of ICMPv6 messages that were dropped because their checksum
           was invalid, or they were IP fragments.";
      }
      leaf type-not-implemented-errors {
        type yang:zero-based-counter64;
        description
          "Count of ICMPv6 messages received that had an unrecognized type.";
      }
      leaf code-not-implemented-errors {
        type yang:zero-based-counter64;
        description
          "Count of ICMPv6 messages received that had an unrecognized code.";
      }
      leaf destination-unreachable {
        type yang:zero-based-counter64;
        description
          "Count of ICMPv6 messages received of type
           'destination unreachable'."; 
      }
      leaf net-unreachable {
        type yang:zero-based-counter64;
        description
          "Count of ICMPv6 'destination unreachable' messages received with
           code 'no route to destination'.";
      }
      leaf destination-denied {
        type yang:zero-based-counter64;
        description
          "Count of ICMPv6 'destination unreachable' messages received with
           code 'communication with destination administratively prohibited'.";
      }
      leaf scope-denied {
        type yang:zero-based-counter64;
        description
          "Count of ICMPv6 'destination unreachable' messages received with
           code 'beyond scope of source address'.";
      }
      leaf host-unreachable {
        type yang:zero-based-counter64;
        description
          "Count of ICMPv6 'destination unreachable' messages received with
           code 'address unreachable'.";
      }
      leaf port-unreachable {
        type yang:zero-based-counter64;
        description
          "Count of ICMPv6 'destination unreachable' messages received with
           code 'port unreachable'.";
      }
      leaf source-denied {
        type yang:zero-based-counter64;
        description
          "Count of ICMPv6 'destination unreachable' messages received with
           code 'source address failed ingress/egress policy'.";
      }
      leaf net-denied {
        type yang:zero-based-counter64;
        description
          "Count of ICMPv6 'destination unreachable' messages received with
           code 'reject route to destination'.";
      }
      leaf packet-too-big {
        type yang:zero-based-counter64;
        description
          "Count of ICMPv6 messages received of type
           'packet too big'.";
      }
      leaf time-exceeded {
        type yang:zero-based-counter64;
        description
          "Count of ICMPv6 messages received of type
           'time exceeded'."; 
      }
      leaf transit-hop-limit-exceeded {
        type yang:zero-based-counter64;
        description
          "Count of ICMPv6 'time exceeded' messages received with code
           'hop limit exceeded in transit'.";
      }
      leaf fragment-reassembly-time-exceeded {
        type yang:zero-based-counter64;
        description
          "Count of ICMPv6 'time exceeded' messages received with code
           'fragment reassembly time exceeded'.";
      }
      leaf parameter-problem {
        type yang:zero-based-counter64;
        description
          "Count of ICMPv6 messages received of type
           'parameter problem'."; 
      }
      leaf header-field-problem {
        type yang:zero-based-counter64;
        description
          "Count of ICMPv6 'parameter exceeded' messages received with code
           'erroneous header field encountered'.";
      }
      leaf next-header-problem {
        type yang:zero-based-counter64;
        description
          "Count of ICMPv6 'parameter exceeded' messages received with code
           'unrecognized next header type encountered'.";
      }
      leaf option-problem {
        type yang:zero-based-counter64;
        description
          "Count of ICMPv6 'parameter exceeded' messages received with code
           'unrecognized IPv6 option encountered'.";
      }
      leaf echo-request {
        type yang:zero-based-counter64;
        description
          "Count of ICMPv6 echo requests handled.";
      }
    }

    // SA state
    list inbound-sa {
      key "queue spi";
      leaf queue { type queue; }
      leaf spi { type spi; }
      description
        "Events for ephemeral inbound security associations (SA).";

      container sa-state {
        leaf rxerrors {
          type yang:zero-based-counter64;
          description
            "Count of all packets destined to this SA that were dropped.";
        }
        leaf protocol-errors {
          type yang:zero-based-counter64;
          description
            "Count of packets that were dropped because the encapsulated
             protocol was not supported.";
        }
        leaf decrypt-errors {
          type yang:zero-based-counter64;
          description
            "Count of packets that were dropped because of errors while
             decapsulating or authenticating the security payload.";
        }
      }
    }

    // KeyManager state
    container key-manager {
      description
        "Authenticated key exchange and SA management events.";

      leaf rxerrors {
        type yang:zero-based-counter64;
        description
          "Total number key exchange requests received that were invalid.";
      }
      leaf route-errors {
        type yang:zero-based-counter64;
        description
          "Count of key exchange requests received that couldn’t be associated
           to any configured route.";
      }
      leaf protocol-errors {
        type yang:zero-based-counter64;
        description
          "Count of key exchange requests received that violated the protocol
           (i.e., order of messages and message format).";
      }
      leaf version-errors {
        type yang:zero-based-counter64;
        description
          "Count of challenges received that specified an incompatible
           version.";
      }
      leaf parameter-errors {
        type yang:zero-based-counter64;
        description
          "Count of challenges received that proposed incompatible AEADs.";
      }
      leaf authentication-errors {
        type yang:zero-based-counter64;
        description
          "Count of key exchange requests received that failed to authenticate
           (i.e., had an erroneous message authentication code.)";
      }
      leaf public-key-errors {
        type yang:zero-based-counter64;
        description
          "Count of key exchange requests received offering public keys that
           were rejected because they were considered unsafe.";
      }
      leaf negotiations-initiated {
        type yang:zero-based-counter64;
        description
          "Count of key exchange negotiations initiated.";
      }
      leaf negotiations-expired {
        type yang:zero-based-counter64;
        description
          "Count of key exchange negotiations expired due to exceeding
           negotiation-ttl.";
      }
      leaf challenges-offered {
        type yang:zero-based-counter64;
        description
          "Count of challenges offered as the protocol responder (elevated
           count can indicate a denial-of-service attempt.)";
      }
      leaf challenges-accepted {
        type yang:zero-based-counter64;
        description
          "Count of challenges accepted as the protocol initator.";
      }
      leaf keypairs-offered {
        type yang:zero-based-counter64;
        description
          "Count of ephemeral key pairs that were offered as the protocol
           responder.";
      }
      leaf keypairs-negotiated {
        type yang:zero-based-counter64;
        description
          "Count of ephemeral key pairs that were negotiated as the protocol
           initiator.";
      }
      leaf inbound-sa-expired {
        type yang:zero-based-counter64;
        description
          "Count of inbound SAs that have expired due to sa-ttl.";
      }
      leaf outbound-sa-expired {
        type yang:zero-based-counter64;
        description
          "Count of outbound SAs that have expired due to sa-ttl.";
      }
      leaf outbound-sa-updated {
        type yang:zero-based-counter64;
        description
          "Count of outbound SAs that were updated.";
      }
    }
  }

}
