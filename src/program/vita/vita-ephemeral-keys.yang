module vita-ephemeral-keys {
  // Metadata
  namespace vita:ephemeral-keys;
  prefix ephemeral-keys;

  // Imports
  import vita-esp-gateway { prefix vita; }

  // Data model:
  // Active outbound SAs (at most one per route) and inbound SAs (possibly
  // multiple per route.) 
  list outbound-sa { uses vita:sa; key "spi"; unique "route"; }
  list inbound-sa { uses vita:sa; key "spi"; }
}
