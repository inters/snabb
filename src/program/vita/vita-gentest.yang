module vita-gentest {
  namespace vita:gentest;
  prefix gentest;

  import vita-esp-gateway { prefix vita; }

  choice gateway {
    case v4 {
      container private-interface4 {
        uses vita:interface; uses vita:interface4;
      }
      list public-interface4 {
        uses vita:interface; uses vita:interface4; uses vita:gateway;
        key ip; unique queue;
      }
    }
    case v6 {
      container private-interface6 {
        uses vita:interface; uses vita:interface6;
      }
      list public-interface6 {
        uses vita:interface; uses vita:interface6; uses vita:gateway;
        key ip; unique queue;
      }
    }
  }

  leaf negotiation-ttl { type vita:time-to-live; }
  leaf sa-ttl { type vita:time-to-live; }

  leaf route-prefix { type string; }
  leaf nroutes { type uint32 { range "1..max"; } }
  leaf packet-size { type string; }
}
